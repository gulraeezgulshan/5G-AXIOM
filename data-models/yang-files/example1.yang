module example1 {
    namespace "http://axiom.com.pk/axiom";
    prefix "axiom";

    organization "AXIOM";
    contact "info@axiom.com.pk";
    description
        "The module for entities implementing the AXIOM system.";

    revision 2020-07-22 {
        description "Initial revision.";
    }

    container system {
        leaf hostname {
            type string;
            mandatory true;
            config true;
            description "Hostname for the network device";
            }
    }
       
}
